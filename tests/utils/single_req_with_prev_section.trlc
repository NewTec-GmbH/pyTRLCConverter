package Requirements

Requirement req_id_1 {
    description = "Pre-section requirement."
}

section "Test section" {
    Requirement req_id_2 {
        description = "Test description"
        precision = 0.01
    }
}
