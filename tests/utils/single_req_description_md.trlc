package Requirements

Requirement req_id_md {
    description =
    '''
    # Heading 1

    ## Heading 2

    - Bullet point 1
    - Bullet point 2
        - Sub bullet point 1
        - Sub bullet point 2

    1. Numbered point 1
    2. Numbered point 2
        1. Sub numbered point 1
        2. Sub numbered point 2

    **Bold text** and *italic text*.

    ```
    Code block example
    ```

    ```plantuml
    @startuml
    Alice -> Bob: Hello
    Bob --> Alice: Hi
    @enduml
    ```

    ---

    > Blockquote example

    [Link to pyTRLCConverter](https://github.com/NewTec-GmbH/pyTRLCConverter)
    '''
}
