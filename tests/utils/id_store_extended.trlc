package Requirements

Requirement req_id_1 {
    description = "Test description"
    index = 1
}

Requirement req_id_2 {
    description = "Additional requirement"
    link        = req_id_1
    index = 2
}
