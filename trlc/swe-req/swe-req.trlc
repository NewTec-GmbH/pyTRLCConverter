package SwRequirements
import AbstractRequirements
import Generic

section "SW Requirements" {

    Generic.Info sw_req_info_about_sw_req {
        description =
        '''
        This file contains the software requirements for the pyTRLCConverter tool.

        The tool supports the following output formats:

        | Format | Subcommand | GFM Support |
        | ------ | ---------- | ----------- |
        | Markdown | `markdown` | yes |
        | reStructuredText | `rst` | yes |
        | docx | `docx` | yes |
        | ReqIF | `reqif` | yes |

        The following picture shows the overall tool flow:
        '''
    }

    Generic.PlantUML sw_req_tool_context_diagram {
        file_path = "../../doc/architecture/context_diagram.puml"
        caption = "pyTRLCConverter Tool Flow"
    }

    section "Functional Requirements" {

        section "General" {

            SwReq sw_req_cli {
                description = "The software shall be a command-line interface (CLI) application."
                verification_criteria = "Every feature shall be accessible via the command line. Therefore its verified by the CLI tests."
                valid_status = AbstractRequirements.VALID_STATUS.valid
            }

            SwReq sw_req_translation {
                description = "The software shall support the requirement type attribute name translation via a translation file in JSON format."
                verification_criteria = "Verify by converting one or more TRLC files with a translation file."
                valid_status = AbstractRequirements.VALID_STATUS.valid
                note = "Some attribute names may contain underscores or other special characters. These shall be translated to a human readable names."
            }

            SwReq sw_req_render_configuration {
                description = "The software shall allow the format of string attributes to be declared per `(package, type, attribute)` pattern via a JSON render configuration file. Supported formats are: `md` (CommonMark), `gfm` (GitHub Flavored Markdown), `rst` (reStructuredText), `xhtml`, and `path` (file-system path to an external image)."
                verification_criteria = "Verify that each supported format token is correctly recognized and applied when a render configuration file is provided."
                valid_status = AbstractRequirements.VALID_STATUS.valid
            }

            SwReq sw_req_prj_spec {
                description = "The software shall support project specific adaptions for the conversion."
                verification_criteria = "Verify by converting one or more TRLC files with a project specific conversion file."
                valid_status = AbstractRequirements.VALID_STATUS.valid
                note = "Every project might have different requirements how the converted output should look like."
            }

            SwReq sw_req_version {
                description = "The software shall provide a version information in the format '<program-name> <major>.<minor>.<patch>'."
                verification_criteria = "Verify by requesting the version information and use the format '<program-name> <major>.<minor>.<patch>'."
                valid_status = AbstractRequirements.VALID_STATUS.valid
            }

            SwReq sw_req_process_trlc_symbols {
                description = "The software shall process all TRLC symbols from the TRLC files."
                verification_criteria = "Verify DumpConverter output against a known good reference."
                valid_status = AbstractRequirements.VALID_STATUS.valid
            }

            SwReq sw_req_destination_format {
                description = "The software shall convert the TRLC files to the required destination format."
                verification_criteria = "Verify by converting to one or more destination formats. Depended on the available formats."
                valid_status = AbstractRequirements.VALID_STATUS.valid
            }

            SwReq sw_req_verbose_mode {
                description = "The software shall show additional conversion information in verbose mode."
                verification_criteria = "Verify by converting one or more TRLC files with the verbose mode enabled."
                valid_status = AbstractRequirements.VALID_STATUS.valid
            }

            SwReq sw_req_error {
                description = "The software shall log any error message on stderr."
                verification_criteria = "Verify by calling the software with no or invalid arguments."
                valid_status = AbstractRequirements.VALID_STATUS.valid
            }
        }

        section "Project Specific Conversion" {
            SwReq sw_req_prj_spec_file {
                description = "The project specific conversion file shall be a Python file."
                verification_criteria = "Verify by converting one or more TRLC files with a project specific conversion file."
                valid_status = AbstractRequirements.VALID_STATUS.valid
                derived = [sw_req_prj_spec]
            }

            SwReq sw_req_prj_spec_interface {
                description = "The project specific conversion interface shall be realized by an abstract interface."
                verification_criteria = "Verify by converting one or more TRLC files with a project specific conversion file."
                valid_status = AbstractRequirements.VALID_STATUS.valid
            }
        }

        section "Command Line Arguments" {

            Generic.Info sw_req_info_cli {
                description = "The following requirements describe the general command line arguments supported by the software. They are independent of the destination format."
            }

            SwReq sw_req_cli_help {
                description = "The software shall support the command line argument '-h' and --help' to show the help information."
                verification_criteria = "Verify by calling the software with the argument '--help' and check if the help information is shown."
                valid_status = AbstractRequirements.VALID_STATUS.valid
            }

            SwReq sw_req_cli_verbose {
                description = "The software shall support the command line argument '-v' and '--verbose' to enable verbose mode."
                verification_criteria = "Verify by calling the software with the argument '--verbose' and check if the verbose output is shown."
                valid_status = AbstractRequirements.VALID_STATUS.valid
                derived = [sw_req_verbose_mode]
            }

            SwReq sw_req_cli_version {
                description = "The software shall support the command line argument '--version' to show the version information."
                verification_criteria = "Verify by calling the software with the argument '--version' and check if the version information is shown."
                valid_status = AbstractRequirements.VALID_STATUS.valid
                derived = [sw_req_version]
            }

            SwReq sw_req_cli_source {
                description = "The software shall support the command line argument '-s' and '--source' multiple times to specify the source file(s) (*.rsl and *.trlc)."
                verification_criteria = "Verify by calling the software with the argument '--source' and check if the source file(s) are used for conversion."
                valid_status = AbstractRequirements.VALID_STATUS.valid
                note = "Source files will be given to TRLC for conversion."
            }

            SwReq sw_req_cli_include {
                description = "The software shall support the command line argument '-i' and '--include' multiple times to specify the file(s) for automatic inclusion."
                verification_criteria = "Verify by calling the software with the argument '--include' and check if the file(s) are included."
                valid_status = AbstractRequirements.VALID_STATUS.valid
                note = "Its equal to TRLC --include program argument."
            }

            SwReq sw_req_cli_exclude {
                description = "The software shall support the command line argument '-ex' and '--exclude' multiple times to specify the file(s) for automatic exclusion."
                verification_criteria = "Verify by calling the software with the argument '--exclude' and check if the file(s) are excluded."
                valid_status = AbstractRequirements.VALID_STATUS.valid
                note = "This is necessary in case an defined architecture element traces to a requirement, but the requirement should not be included in the output."
            }

            SwReq sw_req_no_prj_spec {
                description = "If no project specific conversion file is provided, the software shall use a default conversion."
                verification_criteria = "Verify by converting one or more TRLC files without a project specific conversion file."
                valid_status = AbstractRequirements.VALID_STATUS.valid
            }

            SwReq sw_req_cli_out {
                description = "The software shall support the command line argument '-o' and '--out' to specify the output directory."
                verification_criteria = "Verify by calling the software with the argument '--out' and check if the output is written to the specified directory."
                valid_status = AbstractRequirements.VALID_STATUS.valid
            }

            SwReq sw_req_cli_translation {
                description = "The software shall support the command line argument '-tr' and '--translation' to specify the translation JSON file."
                verification_criteria = "Verify by calling the software with the argument '--translation' and check if the output is written to the specified directory."
                valid_status = AbstractRequirements.VALID_STATUS.valid
            }

            SwReq sw_req_cli_render_cfg {
                description = "The software shall support the command line argument '-rc' and '--renderCfg' to specify the render configuration JSON file."
                verification_criteria = "Verify by calling the software with the argument '--renderCfg' and check if e.g. Markdown is rendered correctly for string literals."
                valid_status = AbstractRequirements.VALID_STATUS.valid
            }

            SwReq sw_req_cli_render_plantuml {
                description = "The Markdown subcommand shall support the command line argument '--render-plantuml' to opt in to rendering plantuml fenced code blocks as SVG image references."
                verification_criteria = "Verify by calling the Markdown converter with '--render-plantuml' and check that plantuml blocks are replaced by SVG image references."
                valid_status = AbstractRequirements.VALID_STATUS.valid
                derived = [sw_req_markdown_render_plantuml]
            }
        }

        section "Markdown" {

            Generic.Info sw_req_info_markdown {
                description = "The following requirements describe the Markdown destination format supported by the software."
            }

            SwReq sw_req_markdown {
                description = "The software shall support the conversion into Markdown format."
                verification_criteria = "Verify by converting one or more TRLC files into Markdown format."
                valid_status = AbstractRequirements.VALID_STATUS.valid
            }

            SwReq sw_req_markdown_section {
                description = "The Markdown converter shall convert a TRLC section into a Markdown heading by considering the depth level."
                verification_criteria = "Verify by converting a TRLC section into a Markdown heading."
                valid_status = AbstractRequirements.VALID_STATUS.valid
            }

            SwReq sw_req_markdown_record {
                description = "The Markdown converter shall convert the attributes of a TRLC record into a Markdown table."
                verification_criteria = "Verify by converting consecutive TRLC records into a Markdown table."
                valid_status = AbstractRequirements.VALID_STATUS.valid
            }

            SwReq sw_req_markdown_escape {
                description = "The software shall escape strings according the Markdown format."
                verification_criteria = "Verify by using strings with characters, which needs escaping."
                valid_status = AbstractRequirements.VALID_STATUS.valid
            }

            SwReq sw_req_markdown_string_format {
                description = "The software shall not escape strings that are already in Markdown format."
                verification_criteria = "Verify by using strings in Markdown format, which needs no escaping."
                valid_status = AbstractRequirements.VALID_STATUS.valid
            }

            SwReq sw_req_markdown_heading {
                description = "The Markdown converter shall provide a function to create a Markdown heading."
                verification_criteria = "Verify by creating a Markdown heading."
                valid_status = AbstractRequirements.VALID_STATUS.valid
            }

            SwReq sw_req_markdown_table {
                description = "The Markdown converter shall provide the functionality to create a Markdown table."
                verification_criteria = "Verify by creating a Markdown table."
                valid_status = AbstractRequirements.VALID_STATUS.valid
            }

            SwReq sw_req_markdown_list {
                description = "The Markdown converter shall provide a function to create a Markdown list, as well as a HTML list."
                verification_criteria = "Verify by creating a Markdown list."
                valid_status = AbstractRequirements.VALID_STATUS.valid
            }

            SwReq sw_req_markdown_link {
                description = "The Markdown converter shall provide a function to create a Markdown link."
                verification_criteria = "Verify by creating a Markdown link."
                valid_status = AbstractRequirements.VALID_STATUS.valid
            }

            SwReq sw_req_markdown_image {
                description = "The Markdown converter shall provide a function to create a Markdown image to embed images."
                verification_criteria = "Verify by creating a Markdown image."
                valid_status = AbstractRequirements.VALID_STATUS.valid
            }

            SwReq sw_req_markdown_text_color {
                description = "The Markdown converter shall provide a function to create colored text in Markdown format."
                verification_criteria = "Verify by creating colored text in Markdown format."
                valid_status = AbstractRequirements.VALID_STATUS.valid
            }

            SwReq sw_req_markdown_soft_return {
                description = "The Markdown converter shall provide a function to convert a line feed to Markdown soft return."
                verification_criteria = "Verify by creating a text with one and more line feeds."
                valid_status = AbstractRequirements.VALID_STATUS.valid
            }

            SwReq sw_req_markdown_out_folder {
                description = "The Markdown converter shall create the converted files in the specified output folder."
                verification_criteria = "Verify by specifying an output folder, that doesn't exist. It must exist after the conversion."
                valid_status = AbstractRequirements.VALID_STATUS.valid
            }

            section "Multiple Documents Mode" {
                SwReq sw_req_markdown_multiple_doc_mode {
                    description = "The software shall create a Markdown file for each TRLC file by default."
                    verification_criteria = "Verify by converting one or more TRLC files into Markdown format and check if a Markdown file is created for each TRLC file."
                    valid_status = AbstractRequirements.VALID_STATUS.valid
                }

                SwReq sw_req_markdown_md_top_level {
                    description = "The software shall add a top level heading to the Markdown file if there is no top level section."
                    verification_criteria = "Verify the top level heading in the Markdown file in multiple doc mode."
                    valid_status = AbstractRequirements.VALID_STATUS.valid
                }
            }

            section "Single Document Mode" {
                SwReq sw_req_markdown_single_doc_mode {
                    description = "The software shall create a single Markdown file which combines all TRLC files if requested by command line arguments."
                    verification_criteria = "Verify by converting one or more TRLC files into Markdown format and check if a single Markdown file is created."
                    valid_status = AbstractRequirements.VALID_STATUS.valid
                }

                SwReq sw_req_markdown_out_file_name_default {
                    description = "The output file name shall be 'output.md' by default."
                    verification_criteria = "Verify by converting one or more TRLC files into Markdown format and check if the output file name is 'output.md'."
                    valid_status = AbstractRequirements.VALID_STATUS.valid
                }

                SwReq sw_req_markdown_out_file_name_custom {
                    description = "The output file name shall be customizable by command line arguments."
                    verification_criteria = "Verify by converting one or more TRLC files into Markdown format and check if the output file name is customizable."
                    valid_status = AbstractRequirements.VALID_STATUS.valid
                }

                SwReq sw_req_markdown_sd_top_level {
                    description = "The software shall add a top level heading to the Markdown file in single doc mode."
                    verification_criteria = "Verify the top level heading in the Markdown file in single doc mode."
                    valid_status = AbstractRequirements.VALID_STATUS.valid
                }

                SwReq sw_req_markdown_top_level_default {
                    description = "The top level heading shall be 'Specification' by default."
                    verification_criteria = "Verify the top level heading in the Markdown file in single doc mode."
                    valid_status = AbstractRequirements.VALID_STATUS.valid
                }

                SwReq sw_req_markdown_top_level_custom {
                    description = "The top level heading shall be customizable by command line arguments."
                    verification_criteria = "Verify by specifying a custom top level heading in the Markdown file in single doc mode."
                    valid_status = AbstractRequirements.VALID_STATUS.valid
                }
            }

            section "Markdown Render Configuration" {

                SwReq sw_req_markdown_render_md {
                    description = "The software shall render strings in [CommonMark's spec v0.31.2](https://spec.commonmark.org/0.31.2/) Markdown format if specified in the render configuration."
                    verification_criteria = "Verify by using strings in Markdown format according to CommonMark's spec, which needs no escaping."
                    valid_status = AbstractRequirements.VALID_STATUS.valid
                }

                SwReq sw_req_markdown_render_gfm {
                    description = "The software shall render strings in [GitHub Flavored Markdown spec v0.29-gfm](https://github.github.com/gfm) Markdown format if specified in the render configuration."
                    verification_criteria = "Verify by using strings in Markdown format according to GitHub Flavored Markdown spec, which needs no escaping."
                    valid_status = AbstractRequirements.VALID_STATUS.valid
                }

                SwReq sw_req_markdown_render_plantuml {
                    description = "When the `--render-plantuml` option is given, the software shall replace fenced code blocks tagged `plantuml` in the Markdown output with SVG image references (`![](plantuml_<hash>.svg)`). The generated SVG file shall be copied to the output folder. If PlantUML is not available, the block shall be replaced by a `[PlantUML error: ...]` paragraph instead of failing the conversion. Without the option, plantuml fenced code blocks shall be passed through unchanged."
                    verification_criteria = "Verify that with `--render-plantuml`, a plantuml fenced code block is replaced by an SVG image reference and the SVG file is present in the output folder. Verify that without the option the block is passed through unchanged. Verify that an unavailable PlantUML yields a `[PlantUML error: ...]` paragraph."
                    valid_status = AbstractRequirements.VALID_STATUS.valid
                }
            }
        }

        section "reStructuredText" {

            Generic.Info sw_req_info_rst {
                description = "The following requirements describe the reStructuredText destination format supported by the software."
            }

            SwReq sw_req_rst {
                description = "The software shall support the conversion into reStructuredText format."
                verification_criteria = "Verify by converting one or more TRLC files into reStructuredText format."
                valid_status = AbstractRequirements.VALID_STATUS.valid
            }

            SwReq sw_req_rst_section {
                description = "The reStructuredText converter shall convert a TRLC section into a reStructuredText heading by considering the depth level."
                verification_criteria = "Verify by converting a TRLC section into a reStructuredText heading."
                valid_status = AbstractRequirements.VALID_STATUS.valid
            }

            SwReq sw_req_rst_record {
                description = "The reStructuredText converter shall convert the attributes of a TRLC record into a reStructuredText admonition with a table."
                verification_criteria = "Verify by converting consecutive TRLC records into a reStructuredText admonition with a table."
                valid_status = AbstractRequirements.VALID_STATUS.valid
            }

            SwReq sw_req_rst_escape {
                description = "The software shall escape all strings according the reStructuredText format."
                verification_criteria = "Verify by using strings with characters, which needs escaping."
                valid_status = AbstractRequirements.VALID_STATUS.valid
            }

            SwReq sw_req_rst_string_format {
                description = "The software shall not escape strings that are already in reStructuredText format."
                verification_criteria = "Verify by using strings in reStructuredText format, which needs no escaping."
                valid_status = AbstractRequirements.VALID_STATUS.valid
            }

            SwReq sw_req_rst_string_format_md {
                description = "The software shall convert strings in Markdown format to reStructuredText format without escaping."
                verification_criteria = "Verify by using strings in Markdown format, which are converted and needs no escaping."
                valid_status = AbstractRequirements.VALID_STATUS.rejected
            }

            SwReq sw_req_rst_heading {
                description = "The reStructuredText converter shall provide a function to create a reStructuredText heading."
                verification_criteria = "Verify by creating a reStructuredText heading."
                valid_status = AbstractRequirements.VALID_STATUS.valid
            }

            SwReq sw_req_rst_admonition {
                description = "The reStructuredText converter shall provide a function to create a reStructuredText admonition."
                verification_criteria = "Verify by creating a reStructuredText admonition."
                valid_status = AbstractRequirements.VALID_STATUS.valid
            }

            SwReq sw_req_rst_table {
                description = "The reStructuredText converter shall provide a function to create a reStructuredText table."
                verification_criteria = "Verify by creating a reStructuredText table."
                valid_status = AbstractRequirements.VALID_STATUS.valid
            }

            SwReq sw_req_rst_list {
                description = "The reStructuredText converter shall provide a function to create a reStructuredText list."
                verification_criteria = "Verify by creating a reStructuredText list."
                valid_status = AbstractRequirements.VALID_STATUS.valid
            }

            SwReq sw_req_rst_link {
                description = "The reStructuredText converter shall provide a function to create a reStructuredText link."
                verification_criteria = "Verify by creating a reStructuredText link."
                valid_status = AbstractRequirements.VALID_STATUS.valid
            }

            SwReq sw_req_rst_image {
                description = "The reStructuredText converter shall provide a function to create a reStructuredText image to embed images."
                verification_criteria = "Verify by creating a reStructuredText image."
                valid_status = AbstractRequirements.VALID_STATUS.valid
            }

            SwReq sw_req_rst_role {
                description = "The reStructuredText converter shall provide a function to create role text in reStructuredText format."
                verification_criteria = "Verify by creating role text in reStructuredText format."
                valid_status = AbstractRequirements.VALID_STATUS.valid
            }

            SwReq sw_req_rst_out_folder {
                description = "The reStructuredText converter shall create the converted files in the specified output folder."
                verification_criteria = "Verify by specifying an output folder, that doesn't exist. It must exist after the conversion."
                valid_status = AbstractRequirements.VALID_STATUS.valid
            }

            section "ReStructuredText Multiple Documents Mode" {
                SwReq sw_req_rst_multiple_doc_mode {
                    description = "The software shall create a reStructuredText file for each TRLC file by default."
                    verification_criteria = "Verify by converting one or more TRLC files into reStructuredText format and check if a reStructuredText file is created for each TRLC file."
                    valid_status = AbstractRequirements.VALID_STATUS.valid
                }
            }

            section "ReStructuredText Single Document Mode" {
                SwReq sw_req_rst_single_doc_mode {
                    description = "The software shall create a single reStructuredText file which combines all TRLC files if requested by command line arguments."
                    verification_criteria = "Verify by converting one or more TRLC files into reStructuredText format and check if a single reStructuredText file is created."
                    valid_status = AbstractRequirements.VALID_STATUS.valid
                }

                SwReq sw_req_rst_out_file_name_default {
                    description = "The output file name shall be 'output.rst' by default."
                    verification_criteria = "Verify by converting one or more TRLC files into reStructuredText format and check if the output file name is 'output.rst'."
                    valid_status = AbstractRequirements.VALID_STATUS.valid
                }

                SwReq sw_req_rst_out_file_name_custom {
                    description = "The output file name shall be customizable by command line arguments."
                    verification_criteria = "Verify by converting one or more TRLC files into reStructuredText format and check if the output file name is customizable."
                    valid_status = AbstractRequirements.VALID_STATUS.valid
                }

                SwReq sw_req_rst_sd_top_level {
                    description = "The software shall add a top level heading to the reStructuredText file in single doc mode."
                    verification_criteria = "Verify the top level heading in the reStructuredText file in single doc mode."
                    valid_status = AbstractRequirements.VALID_STATUS.valid
                }

                SwReq sw_req_rst_sd_top_level_default {
                    description = "The top level heading shall be 'Specification' by default."
                    verification_criteria = "Verify the top level heading in the reStructuredText file in single doc mode."
                    valid_status = AbstractRequirements.VALID_STATUS.valid
                }

                SwReq sw_req_rst_sd_top_level_custom {
                    description = "The top level heading shall be customizable by command line arguments."
                    verification_criteria = "Verify by specifying a custom top level heading in the reStructuredText file in single doc mode."
                    valid_status = AbstractRequirements.VALID_STATUS.valid
                }
            }

            section "ReStructuredText Render Configuration" {

                SwReq sw_req_rst_render_md {
                    description = "The software shall convert strings in [CommonMark's spec v0.31.2](https://spec.commonmark.org/0.31.2/) Markdown format to reStructuredText format if specified in the render configuration."
                    verification_criteria = "Verify by using strings in Markdown format according to CommonMark's spec, that are converted."
                    valid_status = AbstractRequirements.VALID_STATUS.valid
                }

                SwReq sw_req_rst_render_gfm {
                    description = "The software shall convert strings in [GitHub Flavored Markdown spec v0.29-gfm](https://github.github.com/gfm) Markdown format to reStructuredText format if specified in the render configuration."
                    verification_criteria = "Verify by using strings in Markdown format according to GitHub Flavored Markdown spec, that are converted."
                    valid_status = AbstractRequirements.VALID_STATUS.valid
                }

                SwReq sw_req_rst_render_list {
                    description = "The software shall keep the whole content of a Markdown list item inside the list item when converting it to reStructuredText, including continuation lines, nested lists and further paragraphs."
                    verification_criteria = "Verify by converting Markdown lists with wrapped, nested, ordered and multi paragraph items and checking the indentation of the reStructuredText output."
                    valid_status = AbstractRequirements.VALID_STATUS.valid
                }

                SwReq sw_req_rst_render_plantuml {
                    description = "The software shall render fenced code blocks tagged `plantuml` inside Markdown (CommonMark or GFM) requirement attributes as SVG images in the reStructuredText output. The generated SVG file shall be copied to the output folder and referenced via a `.. image::` directive. If PlantUML is not available, the block shall be replaced by a `[PlantUML error: ...]` paragraph instead of failing the conversion."
                    verification_criteria = "Verify that a Markdown requirement attribute containing a fenced ```plantuml``` code block produces a reStructuredText `.. image::` directive referencing an SVG file present in the output folder, and that omitting the PlantUML configuration yields a `[PlantUML error: ...]` paragraph."
                    valid_status = AbstractRequirements.VALID_STATUS.valid
                }
            }
        }

        section "ReqIF" {

            Generic.Info sw_req_info_reqif {
                description = "The following requirements describe the ReqIF destination format supported by the software."
            }

            SwReq sw_req_reqif {
                description = "The software shall support the conversion into ReqIF format v1.2."
                verification_criteria = "Verify by converting one or more TRLC files into ReqIF format."
                valid_status = AbstractRequirements.VALID_STATUS.valid
            }

            SwReq sw_req_reqif_section {
                description = "The ReqIF converter shall convert a TRLC section into a SPEC-HIERARCHY node (no SPEC-OBJECT created) by reusing the last preceding TRLC record's SPEC-OBJECT as the mandatory SPEC-OBJECT-REF. If no preceding record exists, a warning shall be emitted and the section shall be omitted from the hierarchy."
                verification_criteria = "Verify by converting TRLC sections into ReqIF and checking that section names appear only as hierarchy LONG-NAMEs, not in SPEC-OBJECTS, and that the SPEC-OBJECT-REF points to the preceding record."
                valid_status = AbstractRequirements.VALID_STATUS.valid
            }

            SwReq sw_req_reqif_record {
                description = "The ReqIF converter shall convert the attributes of a TRLC record into ReqIF SpecObject attributes."
                verification_criteria = "Verify by converting one or more TRLC records and checking generated ReqIF SpecObjects."
                valid_status = AbstractRequirements.VALID_STATUS.valid
            }

            section "ReqIF Multiple Documents Mode" {
                SwReq sw_req_reqif_multiple_doc_mode {
                    description = "The software shall create a ReqIF file for each TRLC file by default."
                    verification_criteria = "Verify by converting one or more TRLC files into ReqIF and checking one ReqIF file is created for each TRLC file."
                    valid_status = AbstractRequirements.VALID_STATUS.valid
                }
            }

            section "ReqIF Single Document Mode" {
                SwReq sw_req_reqif_single_doc_mode {
                    description = "The software shall create a single ReqIF file which combines all TRLC files if requested by command line arguments."
                    verification_criteria = "Verify by converting one or more TRLC files into ReqIF and checking a single ReqIF file is created."
                    valid_status = AbstractRequirements.VALID_STATUS.valid
                }

                SwReq sw_req_reqif_out_file_name_default {
                    description = "The output file name shall be 'output.reqif' by default."
                    verification_criteria = "Verify by converting one or more TRLC files into ReqIF and check if the output file name is 'output.reqif'."
                    valid_status = AbstractRequirements.VALID_STATUS.valid
                }

                SwReq sw_req_reqif_out_file_name_custom {
                    description = "The output file name shall be customizable by command line arguments."
                    verification_criteria = "Verify by converting one or more TRLC files into ReqIF and check if the output file name is customizable."
                    valid_status = AbstractRequirements.VALID_STATUS.valid
                }

                SwReq sw_req_reqif_top_level_default {
                    description = "The top level heading shall be 'Specification' by default."
                    verification_criteria = "Verify the top level heading in the ReqIF file in single doc mode."
                    valid_status = AbstractRequirements.VALID_STATUS.valid
                }

                SwReq sw_req_reqif_top_level_custom {
                    description = "The top level heading shall be customizable by command line arguments."
                    verification_criteria = "Verify by specifying a custom top level heading in the ReqIF file in single doc mode."
                    valid_status = AbstractRequirements.VALID_STATUS.valid
                }
            }

            section "ReqIF Spec Relations" {

                SwReq sw_req_reqif_relation {
                    description = "The ReqIF converter shall convert a TRLC record reference attribute into a ReqIF SPEC-RELATION between the source and target spec-objects. Array record reference attributes shall produce one SPEC-RELATION per element. The field name shall be used as the relation type long-name."
                    verification_criteria = "Verify by converting TRLC records with record reference fields and checking that the generated ReqIF document contains SPEC-RELATION entries linking source and target spec-objects with the correct relation type."
                    valid_status = AbstractRequirements.VALID_STATUS.valid
                    derived = [sw_req_reqif_record]
                }
            }

            section "ReqIF Archive" {

                SwReq sw_req_reqif_reqifz {
                    description = "The ReqIF converter shall optionally archive the generated .reqif output when --reqifz is given. For each document a subfolder named after the document shall be created inside the output folder, the .reqif file shall be written there, and all files inside that subfolder shall be bundled into a .reqifz ZIP archive placed in the output folder. Each document produces one .reqifz file."
                    verification_criteria = "Verify by converting TRLC files with --reqifz, checking that each document yields one .reqifz archive in the output folder whose contents include the generated .reqif file and any other files in the document subfolder."
                    valid_status = AbstractRequirements.VALID_STATUS.valid
                    derived = [sw_req_reqif]
                }
            }

            section "ReqIF Identifier Persistence" {

                SwReq sw_req_reqif_identifier_immutable {
                    description = "The ReqIF converter shall keep the identifier of every generated ReqIF Identifiable element (SPEC-OBJECT, SPEC-HIERARCHY, SPEC-RELATION and the ReqIF header) immutable across consecutive exports and imports, as required by the ReqIF standard, when an identifier store file is provided via the --id-store command line argument."
                    verification_criteria = "Verify by converting the same TRLC files twice with --id-store pointing to the same JSON file and checking that the identifiers of the generated ReqIF Identifiable elements are unchanged between both exports."
                    valid_status = AbstractRequirements.VALID_STATUS.valid
                    derived = [sw_req_reqif]
                }

                SwReq sw_req_reqif_identifier_store_init {
                    description = "On the initial conversion, when the identifier store file does not yet exist, the ReqIF converter shall generate the identifiers, store them keyed by a stable logical key in the JSON identifier store file, and create that file."
                    verification_criteria = "Verify by converting TRLC files with --id-store pointing to a non-existing JSON file and checking that the file is created and contains the generated identifiers."
                    valid_status = AbstractRequirements.VALID_STATUS.valid
                    derived = [sw_req_reqif_identifier_immutable]
                }

                SwReq sw_req_reqif_identifier_store_reuse {
                    description = "On subsequent conversions the ReqIF converter shall load the identifier store file and reuse the stored identifiers for already known elements. Newly added elements shall receive new identifiers which are added to the identifier store file."
                    verification_criteria = "Verify by converting a TRLC file set with --id-store, then converting an extended file set with the same --id-store and checking that the known elements keep their identifiers while new elements get new identifiers that are written back to the file."
                    valid_status = AbstractRequirements.VALID_STATUS.valid
                    derived = [sw_req_reqif_identifier_immutable]
                }
            }

            section "ReqIF Enumeration" {

                SwReq sw_req_reqif_enum {
                    description = "The ReqIF converter shall convert a TRLC enumeration type attribute into a DATATYPE-DEFINITION-ENUMERATION and emit ATTRIBUTE-VALUE-ENUMERATION for the corresponding spec-object attribute."
                    verification_criteria = "Verify by converting a TRLC record with an enumeration field and checking that the generated ReqIF document contains a DATATYPE-DEFINITION-ENUMERATION and the spec-object contains an ATTRIBUTE-VALUE-ENUMERATION with the correct enum value reference."
                    valid_status = AbstractRequirements.VALID_STATUS.valid
                }

                SwReq sw_req_reqif_enum_key_order {
                    description = "The ENUM-VALUE keys inside a DATATYPE-DEFINITION-ENUMERATION shall start at 0 and be consecutive integers following the declaration order of the literals in the RSL enumeration."
                    verification_criteria = "Verify that ENUM-VALUE KEY attributes in the generated ReqIF file are 0-based consecutive integers ordered as declared in the RSL model."
                    valid_status = AbstractRequirements.VALID_STATUS.valid
                    derived = [sw_req_reqif_enum]
                }

                SwReq sw_req_reqif_enum_null {
                    description = "An optional TRLC enumeration attribute whose value is null shall be omitted from the generated ReqIF spec-object."
                    verification_criteria = "Verify by converting a TRLC record with a null optional enumeration field and checking that the spec-object contains no ATTRIBUTE-VALUE-ENUMERATION for that field."
                    valid_status = AbstractRequirements.VALID_STATUS.valid
                    derived = [sw_req_reqif_enum]
                }
            }

            section "ReqIF Render Configuration" {

                SwReq sw_req_reqif_render_md {
                    description = "The software shall convert strings in [CommonMark's spec v0.31.2](https://spec.commonmark.org/0.31.2/) Markdown format to ReqIF XHTML if specified in the render configuration."
                    verification_criteria = "Verify by using strings in Markdown format according to CommonMark's spec, that are converted to ReqIF XHTML."
                    valid_status = AbstractRequirements.VALID_STATUS.valid
                }

                SwReq sw_req_reqif_render_gfm {
                    description = "The software shall convert strings in [GitHub Flavored Markdown spec v0.29-gfm](https://github.github.com/gfm) Markdown format to ReqIF XHTML if specified in the render configuration."
                    verification_criteria = "Verify by using strings in Markdown format according to GitHub Flavored Markdown spec, that are converted to ReqIF XHTML."
                    valid_status = AbstractRequirements.VALID_STATUS.valid
                }

                SwReq sw_req_reqif_render_xhtml {
                    description = "The software shall pass XHTML content through to the ReqIF XHTML attribute value without modification when the render configuration specifies the `xhtml` format."
                    verification_criteria = "Verify that XHTML content in a requirement attribute is included unchanged (inside the ReqIF XHTML wrapper) in the generated ReqIF output."
                    valid_status = AbstractRequirements.VALID_STATUS.valid
                }

                SwReq sw_req_reqif_render_path {
                    description = "The software shall convert a file path string attribute to a ReqIF XHTML `<object>` element with the MIME type derived from the file extension and a local reference to the file basename when the render configuration specifies the `path` format. The referenced file shall be copied to the output folder so that it is bundled into the .reqifz archive when the `--reqifz` option is used."
                    verification_criteria = "Verify that a requirement attribute configured with the `path` format generates a ReqIF XHTML attribute containing an `<object>` element with a correct `type` (MIME type) and `data` (local file basename) attributes, and that the referenced file is present in the output folder."
                    valid_status = AbstractRequirements.VALID_STATUS.valid
                }

                SwReq sw_req_reqif_render_table_options {
                    description = "The software shall apply optional table rendering options from the render configuration when converting Markdown (CommonMark or GFM) to ReqIF XHTML. Supported options are `border` (a CSS style value applied to the `<table>` element's `style` attribute) and `headingStyle` (a CSS style value applied to each `<th>` cell's `style` attribute)."
                    verification_criteria = "Verify that a GFM attribute configured with `tableOptions` containing `border` and `headingStyle` generates a ReqIF XHTML `<table>` with the specified `style` and `<th>` cells with the specified `style`."
                    valid_status = AbstractRequirements.VALID_STATUS.valid
                }

                SwReq sw_req_reqif_render_plantuml {
                    description = "The software shall render fenced code blocks tagged `plantuml` inside Markdown (CommonMark or GFM) requirement attributes as embedded SVG images in the ReqIF XHTML output. The generated SVG file shall be copied to the output folder (or bundled into the .reqifz archive) and referenced from the XHTML via an `<object>` element with `type=\"image/svg+xml\"` and `data` set to the SVG file's local name. If PlantUML is not available, the block shall be replaced by a `[PlantUML error: ...]` paragraph instead of failing the conversion."
                    verification_criteria = "Verify that a Markdown requirement attribute containing a fenced ```plantuml``` code block produces a ReqIF XHTML `<object type=\"image/svg+xml\">` element, that the referenced SVG file is present in the output folder, and that omitting the PlantUML configuration yields a `[PlantUML error: ...]` paragraph."
                    valid_status = AbstractRequirements.VALID_STATUS.valid
                }
            }
        }

        section "Docx" {

            Generic.Info sw_req_info_docx {
                description = "The following requirements describe the docx destination format supported by the software."
            }

            SwReq sw_req_docx {
                description = "The software shall support the conversion into docx format."
                verification_criteria = "Verify by converting one or more TRLC files into Docx format."
                valid_status = AbstractRequirements.VALID_STATUS.valid
            }

            SwReq sw_req_docx_template {
                description = "The software shall support loading a docx template to append docx content to."
                verification_criteria = "Verify that the generated docx file format starts with the content of the given template."
                valid_status = AbstractRequirements.VALID_STATUS.valid
            }

            SwReq sw_req_docx_file {
                description = "The software shall create a combined docx file for each TRLC file in file read order as provided by TRLC."
                verification_criteria = "Verify by converting one or more TRLC files into docx format and check if a merged docx file is generated as expected."
                valid_status = AbstractRequirements.VALID_STATUS.valid
            }

            SwReq sw_req_docx_section {
                description = "If no project specific conversion file is available, a TRLC section shall be converted into a Docx heading by considering the depth level."
                verification_criteria = "Verify by converting a TRLC section into a docx heading."
                valid_status = AbstractRequirements.VALID_STATUS.valid
            }

            SwReq sw_req_docx_record {
                description = "If no project specific conversion file is available, consecutive TRLC records shall be converted into a docx heading with depth+1, a bookmark and a table listing the attributes."
                verification_criteria = "Verify by converting consecutive TRLC records into a docx file."
                valid_status = AbstractRequirements.VALID_STATUS.valid
            }

            SwReq sw_req_docx_reference {
                description = "If a record attribute of the type 'Record_Reference' is processed, the attribute shall be converted into a hyperlink to the corresponding reference bookmark."
                verification_criteria = "Verify by converting a TRLC record containing a reference to another TRLC record into a docx file."
                valid_status = AbstractRequirements.VALID_STATUS.valid
            }

            section "Docx Render Configuration" {

                SwReq sw_req_docx_render_md {
                    description = "The software shall convert strings in [CommonMark's spec v0.31.2](https://spec.commonmark.org/0.31.2/) Markdown format to docx format if specified in the render configuration."
                    verification_criteria = "Verify by using strings in Markdown format according to CommonMark's spec, that are converted."
                    valid_status = AbstractRequirements.VALID_STATUS.valid
                }

                SwReq sw_req_docx_render_gfm {
                    description = "The software shall convert strings in [GitHub Flavored Markdown spec v0.29-gfm](https://github.github.com/gfm) Markdown format to docx format if specified in the render configuration."
                    verification_criteria = "Verify by using strings in Markdown format according to GitHub Flavored Markdown spec, that are converted."
                    valid_status = AbstractRequirements.VALID_STATUS.valid
                }

                SwReq sw_req_docx_render_plantuml {
                    description = "The software shall render fenced code blocks tagged `plantuml` inside Markdown (CommonMark or GFM) requirement attributes as embedded PNG images in the docx output. If PlantUML is not available, the block shall be replaced by a `[PlantUML error: ...]` paragraph instead of failing the conversion."
                    verification_criteria = "Verify that a Markdown requirement attribute containing a fenced ```plantuml``` code block produces an embedded image in the docx output, and that omitting the PlantUML configuration yields a `[PlantUML error: ...]` paragraph."
                    valid_status = AbstractRequirements.VALID_STATUS.valid
                }
            }
        }

        section "Dump" {

            Generic.Info sw_req_info_dump {
                description = "The following requirements describe the dump destination format supported by the software."
            }

            SwReq sw_req_ascii_conversion {
                description = "The software shall support a simple conversion into text format to console out."
                verification_criteria = "Verify by converting one or more TRLC files using the dump converter."
                valid_status = AbstractRequirements.VALID_STATUS.valid
            }
        }

        section "PlantUML" {

            Generic.Info sw_req_info_plantuml {
                description = "The following requirements describe the PlantUML destination format supported by the software."
            }

            SwReq sw_req_plantuml {
                description = "The software shall support the conversion of a PlantUML diagram to an appropriate image format."
                verification_criteria = "Verify by converting a PlantUML diagram into an appropriate image format."
                valid_status = AbstractRequirements.VALID_STATUS.valid
            }
        }
    }

    section "Constraints" {

        SwConstraint sw_constraint_os_win {
            description = "The software shall support the Windows operating system."
            valid_status = AbstractRequirements.VALID_STATUS.valid
        }

        SwConstraint sw_constraint_os_linux {
            description = "The software shall support the Linux operating system."
            valid_status = AbstractRequirements.VALID_STATUS.valid
        }

        SwConstraint sw_constraint_prg_lang {
            description = "The software shall be implemented in the Python programming language >= v3.10."
            valid_status = AbstractRequirements.VALID_STATUS.valid
            note = "TRLC as 3rd party library may imply additional restrictions on supported versions."
        }

        SwConstraint sw_constraint_pep8 {
            description = "The software shall comply with the PEP8 coding standard."
            valid_status = AbstractRequirements.VALID_STATUS.valid
        }
    }

}
