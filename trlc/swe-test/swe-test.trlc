package SwTests

import Generic
import SwRequirements

section "SW Test Cases" {

    Generic.Info sw_test_info_about_sw_test {
        description = "This file contains the software test cases for the pyTRLCConverter tool."
    }

    section "General" {

        SwTestCase tc_cli {
            description = "This test case checks whether the tool supports the command line arguments."
            verifies = [SwRequirements.sw_req_cli]
        }

        SwTestCase tc_translation {
            description = "This test case check whether the translation of requirement attributes works."
            verifies = [SwRequirements.sw_req_translation]
        }

        SwTestCase tc_render_configuration {
            description = "This test case check whether the render configuration works."
            verifies = [SwRequirements.sw_req_render_configuration]
        }

        SwTestCase tc_prj_spec {
            description = "This test case check whether a project specific converter can be instantiated."
            verifies = [SwRequirements.sw_req_prj_spec, SwRequirements.sw_req_prj_spec_file, SwRequirements.sw_req_prj_spec_interface]
        }

        SwTestCase tc_version {
            description = "This test case check whether '--version' shows the correct version format format <program-name> <major>.<minor>.<patch>."
            verifies = [SwRequirements.sw_req_version, SwRequirements.sw_req_cli_version]
        }

        SwTestCase tc_process_trlc_symbols_one_file_one_req {
            description = "This test case check whether one single TRLC requirement is printed out of one TRLC file."
            verifies = [SwRequirements.sw_req_process_trlc_symbols, SwRequirements.sw_req_destination_format, SwRequirements.sw_req_cli_source]
        }

        SwTestCase tc_process_trlc_symbols_two_files_one_req {
            description = "This test case check whether one single TRLC requirement per TRLC file is printed out of two TRLC files."
            verifies = [SwRequirements.sw_req_process_trlc_symbols, SwRequirements.sw_req_destination_format, SwRequirements.sw_req_cli_source]
        }

        SwTestCase tc_verbose {
            description = "This test case check whether in verbose mode more information is printed out."
            verifies = [SwRequirements.sw_req_verbose_mode, SwRequirements.sw_req_cli_verbose]
        }

        SwTestCase tc_error {
            description = "This test case check whether error messages are printed to stderr."
            verifies = [SwRequirements.sw_req_error]
        }
    }

    section "Project Specific Conversion" {

    }

    section "PlantUML" {

        SwTestCase tc_plantuml {
            description = "This test case checks the conversion of a PlantUML diagram into an image."
            verifies = [SwRequirements.sw_req_plantuml]
        }

    }

    section "Command Line Arguments" {

        SwTestCase tc_help {
            description = "This test case checks whether the help information is shown with '--help' without project specific converter."
            verifies = [SwRequirements.sw_req_cli_help]
        }

        SwTestCase tc_help_prj_spec {
            description = "This test case checks whether the help information is shown with '--help' with project specific converter."
            verifies = [SwRequirements.sw_req_cli_help]
        }

        SwTestCase tc_cli_exclude {
            description = "This test case checks whether a TRLC file can be excluded from the conversion."
            verifies = [SwRequirements.sw_req_cli_exclude]
        }

        SwTestCase tc_cli_include {
            description = "This test case checks whether a TRLC file can be included as on demand context in the conversion."
            verifies = [SwRequirements.sw_req_cli_include]
        }

        SwTestCase tc_cli_translation {
            description = "This test case checks whether a translation file can be configured via the command line."
            verifies = [SwRequirements.sw_req_cli_translation]
        }

        SwTestCase tc_cli_render_cfg {
            description = "This test case checks whether a render configuration file can be configured via the command line."
            verifies = [SwRequirements.sw_req_cli_render_cfg]
        }
    }

    section "Markdown" {

        SwTestCase tc_markdown {
            description = "This test case checks whether the conversion to Markdown format works."
            verifies = [
                SwRequirements.sw_req_markdown,
                SwRequirements.sw_req_markdown_record,
                SwRequirements.sw_req_no_prj_spec,
                SwRequirements.sw_req_cli_out,
                SwRequirements.sw_req_markdown_single_doc_mode,
                SwRequirements.sw_req_markdown_out_file_name_default,
                SwRequirements.sw_req_markdown_sd_top_level,
                SwRequirements.sw_req_markdown_top_level_default]
        }

        SwTestCase tc_markdown_section {
            description = "This test case checks whether the conversion of a TRLC section to a Markdown section works."
            verifies = [
                SwRequirements.sw_req_markdown_section,
                SwRequirements.sw_req_markdown_out_file_name_custom,
                SwRequirements.sw_req_markdown_top_level_custom]
        }

        SwTestCase tc_markdown_escape {
            description = "This test case checks whether the default Markdown converter can convert strings with Markdown escaping."
            verifies = [SwRequirements.sw_req_markdown_escape]
        }

        SwTestCase tc_markdown_heading {
            description = '''This test case checks whether the default Markdown converter provides a function
             to create valid Markdown headings.'''
            verifies = [SwRequirements.sw_req_markdown_heading]
        }

        SwTestCase tc_markdown_table {
            description = '''This test case checks whether the default Markdown converter provides the functionality
             to create valid Markdown tables.'''
            verifies = [SwRequirements.sw_req_markdown_table]
        }

        SwTestCase tc_markdown_list {
            description = '''This test case checks whether the default Markdown converter provides a function
             to create valid Markdown list and a valid HTML list.'''
            verifies = [SwRequirements.sw_req_markdown_list]
        }

        SwTestCase tc_markdown_link {
            description = '''This test case checks whether the default Markdown converter provides a function
             to create valid Markdown links.'''
            verifies = [SwRequirements.sw_req_markdown_link]
        }

        SwTestCase tc_markdown_image {
            description = '''This test case checks whether the default Markdown converter provides a function
             to embed images in Markdown.'''
            verifies = [SwRequirements.sw_req_markdown_image]
        }

        SwTestCase tc_markdown_text_color {
            description = '''This test case checks whether the default Markdown converter provides a function
             to create colored text in Markdown.'''
            verifies = [SwRequirements.sw_req_markdown_text_color]
        }

        SwTestCase tc_markdown_soft_return {
            description = '''This test case checks whether the default Markdown converter provides a function
             to encode line feeds as Markdown soft returns.'''
            verifies = [SwRequirements.sw_req_markdown_soft_return]
        }

        SwTestCase tc_markdown_out_folder {
            description = '''This test case checks whether the default Markdown converter creates output files in the
             specified output folder.'''
            verifies = [SwRequirements.sw_req_markdown_out_folder]
        }

        SwTestCase tc_markdown_multi_doc {
            description = '''This test case checks whether the conversion to markdown in multiple document mode creates one output document per TRLC source file and
             whether the top level heading is created when required.'''
            verifies = [SwRequirements.sw_req_markdown_multiple_doc_mode, SwRequirements.sw_req_markdown_md_top_level]
        }

        SwTestCase tc_markdown_render_md {
            description = '''This test case checks whether CommonMark Markdown content in requirement attributes is rendered correctly
             when the render configuration is set to "md".'''
            verifies = [SwRequirements.sw_req_markdown_render_md, SwRequirements.sw_req_markdown_string_format]
        }

        SwTestCase tc_markdown_render_gfm {
            description = '''This test case checks whether GitHub Flavored Markdown content in requirement attributes is rendered correctly
             when the render configuration is set to "gfm".'''
            verifies = [SwRequirements.sw_req_markdown_render_gfm, SwRequirements.sw_req_markdown_string_format]
        }

        SwTestCase tc_markdown_render_plantuml {
            description = '''This test case checks whether a fenced ```plantuml``` code block inside a Markdown requirement attribute is
             replaced by an SVG image reference when --render-plantuml is given, and that the SVG file is written to the output folder.'''
            verifies = [SwRequirements.sw_req_markdown_render_plantuml, SwRequirements.sw_req_cli_render_plantuml, SwRequirements.sw_req_plantuml]
        }

        SwTestCase tc_markdown_render_plantuml_error {
            description = '''This test case checks whether a fenced ```plantuml``` code block is replaced by a [PlantUML error: ...]
             paragraph in the Markdown output when --render-plantuml is given but PlantUML is not available.'''
            verifies = [SwRequirements.sw_req_markdown_render_plantuml]
        }
    }

    section "reStructuredText" {

        SwTestCase tc_rst {
            description = "This test case checks whether the conversion to reStructuredText format works."
            verifies = [
                SwRequirements.sw_req_rst,
                SwRequirements.sw_req_rst_record,
                SwRequirements.sw_req_no_prj_spec,
                SwRequirements.sw_req_cli_out,
                SwRequirements.sw_req_rst_single_doc_mode,
                SwRequirements.sw_req_rst_out_file_name_default,
                SwRequirements.sw_req_rst_sd_top_level,
                SwRequirements.sw_req_rst_sd_top_level_default]
        }

        SwTestCase tc_rst_section {
            description = "This test case checks whether the conversion of a TRLC section to a reStructuredText section works."
            verifies = [SwRequirements.sw_req_rst_section]
        }

        SwTestCase tc_rst_escape {
            description = "This test case checks whether the default reStructuredText converter can convert strings with reStructuredText escaping."
            verifies = [SwRequirements.sw_req_rst_escape]
        }

        SwTestCase tc_rst_heading {
            description = '''This test case checks whether the default reStructuredText converter provides a function
             to create valid reStructuredText headings.'''
            verifies = [SwRequirements.sw_req_rst_heading]
        }

        SwTestCase tc_rst_admonition {
            description = '''This test case checks whether the default reStructuredText converter provides a function
             to create valid reStructuredText admonition.'''
            verifies = [SwRequirements.sw_req_rst_admonition]
        }

        SwTestCase tc_rst_table {
            description = '''This test case checks whether the default reStructuredText converter provides the functionality
             to create valid reStructuredText tables.'''
            verifies = [SwRequirements.sw_req_rst_table]
        }

        SwTestCase tc_rst_list {
            description = '''This test case checks whether the default reStructuredText converter provides a function
             to create valid reStructuredText list.'''
            verifies = [SwRequirements.sw_req_rst_list]
        }

        SwTestCase tc_rst_link {
            description = '''This test case checks whether the default reStructuredText converter provides a function
             to create valid reStructuredText links.'''
            verifies = [SwRequirements.sw_req_rst_link]
        }

        SwTestCase tc_rst_image {
            description = '''This test case checks whether the default reStructuredText converter provides a function
             to embed images in reStructuredText.'''
            verifies = [SwRequirements.sw_req_rst_image]
        }

        SwTestCase tc_rst_role {
            description = '''This test case checks whether the default reStructuredText converter provides a function
             to create colored text in reStructuredText.'''
            verifies = [SwRequirements.sw_req_rst_role]
        }

        SwTestCase tc_rst_out_folder {
            description = '''This test case checks whether the default reStructuredText converter creates output files in the
             specified output folder.'''
            verifies = [SwRequirements.sw_req_rst_out_folder]
        }

        SwTestCase tc_rst_single_doc_custom {
            description = "This test case checks whether the conversion to reStructuredText in single document mode is customizeable."
            verifies = [SwRequirements.sw_req_rst_out_file_name_custom, SwRequirements.sw_req_rst_sd_top_level_custom]
        }

        SwTestCase tc_rst_multi_doc {
            description = "This test case checks whether the conversion to reStructuredText in multiple document mode convers one output document per TRLC source file."
            verifies = [SwRequirements.sw_req_rst_multiple_doc_mode]
        }

        SwTestCase tc_rst_string_format {
            description = "This test case checks that strings already in reStructuredText format are not escaped."
            verifies = [SwRequirements.sw_req_rst_string_format]
        }

        SwTestCase tc_rst_render_md {
            description = '''This test case checks whether CommonMark Markdown content in requirement attributes is rendered correctly
             when the render configuration is set to "md".'''
            verifies = [SwRequirements.sw_req_rst_render_md]
        }

        SwTestCase tc_rst_render_gfm {
            description = '''This test case checks whether GitHub Flavored Markdown content in requirement attributes is rendered correctly
             when the render configuration is set to "gfm".'''
            verifies = [SwRequirements.sw_req_rst_render_gfm]
        }

        SwTestCase tc_rst_render_list {
            description = '''This test case checks whether wrapped, nested, ordered and multi paragraph Markdown list items
             are converted into reStructuredText list items, which keep their whole content, for CommonMark and GFM.'''
            verifies = [SwRequirements.sw_req_rst_render_list]
        }

        SwTestCase tc_rst_render_plantuml {
            description = '''This test case checks whether a fenced ```plantuml``` code block inside a Markdown requirement attribute is
             rendered as a reStructuredText ``.. image::`` directive referencing an SVG file written to the output folder.'''
            verifies = [SwRequirements.sw_req_rst_render_plantuml, SwRequirements.sw_req_plantuml]
        }

        SwTestCase tc_rst_render_plantuml_error {
            description = '''This test case checks whether a fenced ```plantuml``` code block is replaced by a [PlantUML error: ...]
             paragraph in the generated RST output when the PLANTUML environment variable is not configured, so the conversion
             does not fail.'''
            verifies = [SwRequirements.sw_req_rst_render_plantuml]
        }
    }

    section "ReqIF" {

        SwTestCase tc_reqif {
            description = "This test case checks whether the conversion to ReqIF format works."
            verifies = [
                SwRequirements.sw_req_reqif,
                SwRequirements.sw_req_reqif_record,
                SwRequirements.sw_req_no_prj_spec,
                SwRequirements.sw_req_cli_out,
                SwRequirements.sw_req_reqif_single_doc_mode,
                SwRequirements.sw_req_reqif_out_file_name_default,
                SwRequirements.sw_req_reqif_top_level_default]
        }

        SwTestCase tc_reqif_section {
            description = "This test case checks whether a TRLC section produces a SPEC-HIERARCHY node referencing the preceding record's SPEC-OBJECT, and that a warning is emitted when no preceding record exists."
            verifies = [SwRequirements.sw_req_reqif_section]
        }

        SwTestCase tc_reqif_single_doc_custom {
            description = "This test case checks whether the conversion to ReqIF in single document mode is customizable."
            verifies = [SwRequirements.sw_req_reqif_out_file_name_custom, SwRequirements.sw_req_reqif_top_level_custom]
        }

        SwTestCase tc_reqif_render_md {
            description = '''This test case checks whether CommonMark Markdown content in requirement attributes is rendered correctly
             when the render configuration is set to "md".'''
            verifies = [SwRequirements.sw_req_reqif_render_md]
        }

        SwTestCase tc_reqif_render_gfm {
            description = '''This test case checks whether GitHub Flavored Markdown content in requirement attributes is rendered correctly
             when the render configuration is set to "gfm".'''
            verifies = [SwRequirements.sw_req_reqif_render_gfm]
        }

        SwTestCase tc_reqif_render_xhtml {
            description = '''This test case checks whether XHTML content in requirement attributes is passed through without modification
             when the render configuration is set to "xhtml".'''
            verifies = [SwRequirements.sw_req_reqif_render_xhtml]
        }

        SwTestCase tc_reqif_render_table_options {
            description = '''This test case checks whether GFM table rendering options (`border` and `headingStyle`) from the render
             configuration are applied to the generated ReqIF XHTML, producing a `<table>` with the configured `style` and `<th>`
             cells with the configured `style`.'''
            verifies = [SwRequirements.sw_req_reqif_render_table_options]
        }

        SwTestCase tc_reqif_render_path {
            description = '''This test case checks whether a file path attribute is rendered as a ReqIF XHTML <object> element with the
             correct MIME type and local file reference, and that the referenced file is copied to the output folder.'''
            verifies = [SwRequirements.sw_req_reqif_render_path]
        }

        SwTestCase tc_reqif_render_path_reqifz {
            description = '''This test case checks whether the external file referenced by a path format attribute is included in the
             .reqifz archive when the --reqifz option is used.'''
            verifies = [SwRequirements.sw_req_reqif_render_path]
        }

        SwTestCase tc_reqif_render_plantuml {
            description = '''This test case checks whether a fenced ```plantuml``` code block inside a Markdown requirement attribute is
             rendered as an XHTML <object type="image/svg+xml"> element in the generated ReqIF output and that the referenced SVG file
             is written to the output folder.'''
            verifies = [SwRequirements.sw_req_reqif_render_plantuml, SwRequirements.sw_req_plantuml]
        }

        SwTestCase tc_reqif_render_plantuml_error {
            description = '''This test case checks whether a fenced ```plantuml``` code block is replaced by a [PlantUML error: ...]
             paragraph in the generated ReqIF output when the PLANTUML environment variable is not configured, so the conversion
             does not fail.'''
            verifies = [SwRequirements.sw_req_reqif_render_plantuml]
        }

        SwTestCase tc_reqif_enum {
            description = "This test case checks whether a TRLC enumeration attribute is converted to a DATATYPE-DEFINITION-ENUMERATION with 0-based consecutive ENUM-VALUE keys and emitted as ATTRIBUTE-VALUE-ENUMERATION in the spec-object."
            verifies = [SwRequirements.sw_req_reqif_enum, SwRequirements.sw_req_reqif_enum_key_order]
        }

        SwTestCase tc_reqif_enum_null {
            description = "This test case checks whether an optional TRLC enumeration attribute with a null value is omitted from the generated ReqIF spec-object."
            verifies = [SwRequirements.sw_req_reqif_enum_null]
        }

        SwTestCase tc_reqif_relation {
            description = "This test case checks whether TRLC record reference attributes are converted to ReqIF SPEC-RELATION entries, and that array record reference attributes produce one SPEC-RELATION per element."
            verifies = [SwRequirements.sw_req_reqif_relation]
        }

        SwTestCase tc_reqif_reqifz {
            description = "This test case checks whether the ReqIF converter archives the generated output as a .reqifz ZIP file when the --reqifz flag is given."
            verifies = [SwRequirements.sw_req_reqif_reqifz]
        }

        SwTestCase tc_reqif_identifier_store_init {
            description = "This test case checks whether the ReqIF converter creates the JSON identifier store file and stores the generated identifiers on the initial conversion when --id-store points to a non-existing file."
            verifies = [SwRequirements.sw_req_reqif_identifier_store_init]
        }

        SwTestCase tc_reqif_identifier_immutable {
            description = "This test case checks whether the identifiers of the generated ReqIF Identifiable elements stay immutable across two consecutive exports using the same --id-store file."
            verifies = [SwRequirements.sw_req_reqif_identifier_immutable]
        }

        SwTestCase tc_reqif_identifier_store_reuse {
            description = "This test case checks whether the ReqIF converter reuses stored identifiers for known elements and assigns new identifiers to new elements, writing them back to the --id-store file."
            verifies = [SwRequirements.sw_req_reqif_identifier_store_reuse]
        }
    }

    section "Docx" {

        SwTestCase tc_docx {
            description = "This test case checks whether the conversion to docx format works."
            verifies = [SwRequirements.sw_req_docx, SwRequirements.sw_req_docx_record]
        }

        SwTestCase tc_docx_multiple {
            description = "This test case checks whether the conversion of multiple records containing record_references to docx format works."
            verifies = [SwRequirements.sw_req_docx_record, SwRequirements.sw_req_docx_reference]
        }

        SwTestCase tc_docx_section {
            description = "This test case checks whether the conversion of a TRLC section to a docx section works."
            verifies = [SwRequirements.sw_req_docx_section]
        }

        SwTestCase tc_docx_file {
            description = "This test case checks whether the conversion to docx combines the results from multiple TRLC files into one docx file"
            verifies = [SwRequirements.sw_req_docx_file]
        }

        SwTestCase tc_docx_template {
            description = "This test case checks whether the conversion using a template works correctly."
            verifies = [SwRequirements.sw_req_docx_template]
        }

        SwTestCase tc_docx_render_md {
            description = "this test case checks whether the conversion from CommonMark Markdown strings to docx works correctly."
            verifies = [SwRequirements.sw_req_docx_render_md]
        }

        SwTestCase tc_docx_render_gfm {
            description = "This test case checks whether GitHub Flavored Markdown content in requirement attributes is rendered correctly when the render configuration is set to \"gfm\"."
            verifies = [SwRequirements.sw_req_docx_render_gfm]
        }

        SwTestCase tc_docx_render_plantuml {
            description = '''This test case checks whether a fenced ```plantuml``` code block inside a Markdown requirement attribute is
             rendered as an embedded PNG image in the docx output, or replaced by a [PlantUML error: ...] paragraph if PlantUML is
             not available.'''
            verifies = [SwRequirements.sw_req_docx_render_plantuml, SwRequirements.sw_req_plantuml]
        }
    }

    section "Dump" {

        SwTestCase tc_ascii_conversion {
            description = "This test case checks whether the conversion to ASCII format works."
            verifies = [SwRequirements.sw_req_ascii_conversion]
        }
    }
}
