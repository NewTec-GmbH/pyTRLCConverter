package SwArch

import Generic
import SwRequirements

section "SW Architecture" {

    Generic.Info sw_arch_info_about {
        description =
            """
            This file contains the software architecture for the pyTRLCConverter tool.

            pyTRLCConverter is a command-line tool to convert TRLC files to different output formats, e.g. Markdown, reStructuredText or docx.

            A main challenge for pyTRLCConverter is the conversion of project-specific TRLC types. TRLC is a framework that gets adapted to
            project needs using "rsl" files. These files define TRLC types through derivations similar to classes in OOP.
            PyTRLCConverter uses built-in converter classes that convert to destination formats using a generic `attribute:value` style
            result. These built-in converter can be extended in an object-oriented manner to understand user defined types.

            The following table gives an overview of the supported output formats:

            | Format | Subcommand | GFM Support |
            | ------ | ---------- | ----------- |
            | Markdown | `markdown` | yes |
            | reStructuredText | `rst` | yes |
            | docx | `docx` | yes |
            | ReqIF | `reqif` | yes |

            The following picture shows the overall tool flow:
            """
    }

    Generic.PlantUML sw_arch_flow_diagram {
        caption = "pyTRLCConverter Tool Flow"
        file_path ="../../doc/architecture/context_diagram.puml"
    }

    section "General" {
        SwArchSpec sw_arch_python_python {
            description = "The pyTRLCConverter tool is implemented using Python v3.10 or higher and additional libraries available for Windows and Linux operating systems."
            verification_criteria = "CI testing on Linux and Windows hosts."
            satisfies = [
                SwRequirements.sw_constraint_os_win,
                SwRequirements.sw_constraint_os_linux,
                SwRequirements.sw_constraint_prg_lang,
            ]
        }

        SwArchSpec sw_arch_python_style {
            description = "The pyTRLCConverter Python implementation files follow the PEP8 coding standard. Check code using `pylint` in development and CI."
            verification_criteria = "CI check using pylint on Linux and Windows hosts."
            satisfies = [
                SwRequirements.sw_constraint_pep8
            ]
        }

        SwArchSpec sw_arch_cli_tool {
            description = "The pyTRLCConverter tool is a command line application driven by arguments."
            verification_criteria = "Call the tool using the `pyTRLCConverter` frontend. Check console output."
            satisfies = [SwRequirements.sw_req_cli]
        }

        SwArchSpec sw_arch_error_msgs {
            description = "The pyTRLCConverter tool writes informal messages to stdout and error messages to stderr."
            verification_criteria = "Call the tool using the `pyTRLCConverter` frontend with legal and wrong arguments. Check console output."
            satisfies = [SwRequirements.sw_req_error]
        }

        section "Static View" {
            Generic.Info sw_arch_info_static {
                description = "The following diagram shows the static architecture of the tool. It contains the components (Python modules) and their relations."
            }

            Generic.PlantUML sw_arch_class_diagram {
                caption = "Static Architecture view"
                file_path ="../../doc/architecture/class_diagram.puml"
            }
        }

        section "Dynamic View" {
            Generic.Info sw_arch_info_dynamic {
                description =
                """
                The following diagram shows the pyTRLCConverter runtime view using a sequence_diagram.
                There are 4 main phases:

                * Processing of command-line arguments.
                * Loading of converter classes.
                * Loading of all TRLC files.
                * Traversing and conversion of TRLC sections and records.
                """
            }

            Generic.PlantUML sw_arch_sequence_diagram {
                caption = "Dynamic Architecture View"
                file_path ="../../doc/architecture/sequence_diagram.puml"
            }
        }
    }

    section "Concepts" {
        Generic.Info sw_arch_concept_section {
                description =
                """
                This sections explains the major concepts used in pyTRLCConverter.
                """
        }

        section "Converter Derivation Concept" {
            Generic.Info sw_arch_concept_converter_generic {
                description =
                """
                pyTRLCConverter uses a multilevel class hierarchy for providing different
                output formats and user defined type conversions. Only the ProjectConverter
                derivation level must be provided by a project using pyTRLCConverter. The
                upper base class levels are part of pyTRLCConverter.
                """
            }
            Generic.PlantUML sw_arch_concept_converter_diagram {
                    caption = "Class Diagram Derivation Concept"
                    file_path ="../../doc/architecture/concepts/concept_converter_derivation.puml"
            }
        }

         section "Text Formatting" {
            Generic.Info sw_arch_concept_text_formatting {
                description =
                """
                **Attribute Translation**

                TRLC attributes are key/value pairs inside a TRLC type, but not necessarily nice for
                documentation. The pyTRLCConverter converters provide a translation concept to map
                attribute names defined in a json translation file. It is a dictionary of type names.
                Each entry is another dictionary to map the attribute names of this type to the
                displayed text.

                Example for a type "SwReg":

                ```
                {
                    "SwReq": {
                        "description": "Description",
                        "valid_status": "Valid Status",
                        "verification_criteria": "Verification Criteria",
                    }

                }
                ```

                **Text Rendering**

                pyTRLCConverter can render text attributes from Markdown into the destination format.
                A render configuration file is used to define which attributes contain Markdown formatting.
                This is another json file. The matching is done using regular expressions. The first matching
                entry in the render configuration list is used.

                Example: Define the attribute description for type SwArchSpec in any package to be in Markdown.

                ```
                {
                   "renderCfg":
                   [
                       {
                           "package": ".*",
                           "type": "SwArchSpec",
                           "attribute": "description",
                           "format": "md"
                       }
                   ]
                }
                ```
                """
            }
        }

    }

    section "Components" {
        Generic.Info sw_arch_comp_section {
                description =
                """
                This sections shows details of the major components of pyTRLCConverter.
                """
        }
        section "main" {
            Generic.PlantUML sw_arch_comp_main_diagram {
                    caption = "Internal Functions and Dependencies in __main__.py"
                    file_path ="../../doc/architecture/components/comp_main.puml"
            }
            SwArchSpec sw_arch_component_main {
                description =
                    """
                    The **main** component is the application entry point. It handles argument handling,
                    help printing, usage error handling and version printing.

                    Embedded Blocks:

                    * main entry point
                    * command-line argument processing
                    * rendering configuration
                    * converter loading
                    """
                verification_criteria = "Call the tool using the `pyTRLCConverter` frontend with supported and unsupported arguments. Check console output."
                satisfies = [
                    SwRequirements.sw_req_render_configuration,
                    SwRequirements.sw_req_prj_spec,
                    SwRequirements.sw_req_prj_spec_file,
                    SwRequirements.sw_req_cli_help,
                    SwRequirements.sw_req_cli_verbose,
                    SwRequirements.sw_req_cli_source,
                    SwRequirements.sw_req_cli_include,
                    SwRequirements.sw_req_cli_exclude,
                    SwRequirements.sw_req_no_prj_spec,
                    SwRequirements.sw_req_cli_out,
                    SwRequirements.sw_req_cli_translation,
                    SwRequirements.sw_req_cli_render_cfg,
                    SwRequirements.sw_req_destination_format
                ]
            }
        }
        section "ItemWalker" {
            Generic.PlantUML sw_arch_comp_itemwalker_diagram {
                    caption = "Class Diagram for ItemWalker"
                    file_path ="../../doc/architecture/components/comp_item_walker.puml"
            }
            SwArchSpec sw_arch_component_itemwalker {
                description =
                    """
                    The ItemWalker class is responsible for traversing the TRLC symbol table,
                    which holds all TRLC elements. The selected converter is then applied to
                    all of the elements.

                    * Get TRLC symbol table
                    * Traverse the symbol table
                    * Call converter for each TRLC element
                    """
                verification_criteria = "Call the tool using the `pyTRLCConverter` frontend with dump converter and compare against a reference."
                satisfies = [
                    SwRequirements.sw_req_process_trlc_symbols,
                ]
            }
        }
        section "Base Converter" {
            Generic.PlantUML sw_arch_comp_base_converter_diagram {
                    caption = "Class Diagram for BaseConverter"
                    file_path ="../../doc/architecture/components/comp_base_converter.puml"
            }
            SwArchSpec sw_arch_component_base_converter {
                description =
                    """
                    The base converter implements the abstract converter API with logic
                    that is common between all format specific converter implementations.

                    * Render configuration handling
                    * Attribute translations
                    * Generic record conversion
                    """
                verification_criteria = "Call the tool using the `pyTRLCConverter` with Dump Converter and both render and translation configurations."
                satisfies = [
                    SwRequirements.sw_req_translation,
                    SwRequirements.sw_req_rst_render_md,
                    SwRequirements.sw_req_rst_render_gfm,
                    SwRequirements.sw_req_prj_spec_interface
                ]
            }
        }
        section "Dump Converter" {
            Generic.PlantUML sw_arch_comp_dump_converter_diagram {
                    caption = "Class Diagram for Dump-Converter"
                    file_path ="../../doc/architecture/components/comp_dump_converter.puml"
            }
            SwArchSpec sw_arch_component_dump_converter {
                description =
                    """
                    The Dump Converter implements the Text output conversion.

                    * Registers the `dump` output format and options
                    * Prints sections and records to console
                    """
                verification_criteria = "Call the tool using the `pyTRLCConverter` frontend with dump output format."
                satisfies = [
                    SwRequirements.sw_req_ascii_conversion,
                    SwRequirements.sw_req_no_prj_spec,
                    SwRequirements.sw_req_destination_format
                ]
            }
        }
        section "Markdown Converter" {
            Generic.PlantUML sw_arch_comp_markdown_converter_diagram {
                    caption = "Class Diagram for Markdown-Converter"
                    file_path ="../../doc/architecture/components/comp_markdown_converter.puml"
            }
            SwArchSpec sw_arch_component_markdown_converter {
                description =
                    """
                    The Markdown Converter implements the Markdown output format conversion.

                    * Registers the `markdown` output format and options
                    * Prints sections and records in markdown
                    * Optionally renders inline PlantUML fenced code blocks as SVG image references when `--render-plantuml` is given.
                    """
                verification_criteria = "Call the tool using the `pyTRLCConverter` frontend with markdown output format."
                satisfies = [
                    SwRequirements.sw_req_markdown,
                    SwRequirements.sw_req_markdown_section,
                    SwRequirements.sw_req_markdown_record,
                    SwRequirements.sw_req_markdown_escape,
                    SwRequirements.sw_req_markdown_string_format,
                    SwRequirements.sw_req_markdown_heading,
                    SwRequirements.sw_req_markdown_table,
                    SwRequirements.sw_req_markdown_list,
                    SwRequirements.sw_req_markdown_link,
                    SwRequirements.sw_req_markdown_image,
                    SwRequirements.sw_req_markdown_text_color,
                    SwRequirements.sw_req_markdown_soft_return,
                    SwRequirements.sw_req_markdown_out_folder,
                    SwRequirements.sw_req_markdown_multiple_doc_mode,
                    SwRequirements.sw_req_markdown_md_top_level,
                    SwRequirements.sw_req_markdown_single_doc_mode,
                    SwRequirements.sw_req_markdown_out_file_name_custom,
                    SwRequirements.sw_req_markdown_sd_top_level,
                    SwRequirements.sw_req_markdown_top_level_default,
                    SwRequirements.sw_req_markdown_top_level_custom,
                    SwRequirements.sw_req_markdown_render_md,
                    SwRequirements.sw_req_markdown_render_gfm,
                    SwRequirements.sw_req_markdown_render_plantuml,
                    SwRequirements.sw_req_cli_render_plantuml,
                    SwRequirements.sw_req_markdown_out_file_name_default,
                    SwRequirements.sw_req_destination_format
                ]
            }
        }
        section "ReStructuredText Converter" {
            Generic.PlantUML sw_arch_comp_rst_converter_diagram {
                    caption = "Class Diagram for ReStructuredText-Converter"
                    file_path ="../../doc/architecture/components/comp_rst_converter.puml"
            }
            SwArchSpec sw_arch_component_rst_converter {
                description =
                    """
                    The ReStructuredText Converter implements the ReStructuredText format output conversion.

                    * Registers the `rst` output format and options
                    * Prints sections and records in ReStructuredText
                    * Renders inline PlantUML fenced code blocks as SVG images referenced via `.. image::` directives.
                    """
                verification_criteria = "Call the tool using the `pyTRLCConverter` frontend with rst output format."
                satisfies = [
                    SwRequirements.sw_req_rst,
                    SwRequirements.sw_req_rst_section,
                    SwRequirements.sw_req_rst_record,
                    SwRequirements.sw_req_rst_escape,
                    SwRequirements.sw_req_rst_string_format,
                    SwRequirements.sw_req_rst_heading,
                    SwRequirements.sw_req_rst_admonition,
                    SwRequirements.sw_req_rst_table,
                    SwRequirements.sw_req_rst_list,
                    SwRequirements.sw_req_rst_link,
                    SwRequirements.sw_req_rst_image,
                    SwRequirements.sw_req_rst_role,
                    SwRequirements.sw_req_rst_out_folder,
                    SwRequirements.sw_req_rst_multiple_doc_mode,
                    SwRequirements.sw_req_rst_single_doc_mode,
                    SwRequirements.sw_req_rst_out_file_name_default,
                    SwRequirements.sw_req_rst_out_file_name_custom,
                    SwRequirements.sw_req_rst_sd_top_level,
                    SwRequirements.sw_req_rst_sd_top_level_default,
                    SwRequirements.sw_req_rst_sd_top_level_custom,
                    SwRequirements.sw_req_rst_render_md,
                    SwRequirements.sw_req_rst_render_gfm,
                    SwRequirements.sw_req_rst_render_list,
                    SwRequirements.sw_req_rst_render_plantuml,
                    SwRequirements.sw_req_destination_format
                ]
            }
        }
        section "ReqIF Converter" {
            Generic.PlantUML sw_arch_comp_reqif_converter_diagram {
                    caption = "Class Diagram for ReqIF-Converter"
                    file_path ="../../doc/architecture/components/comp_reqif_converter.puml"
            }
            SwArchSpec sw_arch_component_reqif_converter {
                description =
                    """
                    The ReqIF Converter implements the ReqIF output format conversion.

                    * Registers the `reqif` output format and options.
                    * Creates sections and records in ReqIF format.
                    * Converts configured CommonMark and GFM fields into ReqIF XHTML.
                    * Passes configured XHTML fields through to ReqIF XHTML without modification.
                    * Renders inline PlantUML fenced code blocks as embedded SVG images in XHTML attributes.
                    * Converts TRLC enumeration type attributes to DATATYPE-DEFINITION-ENUMERATION with 0-based consecutive ENUM-VALUE keys in RSL declaration order.
                    * Omits optional enumeration attributes with null value from the generated spec-object.
                    * Converts TRLC record reference attributes to ReqIF SPEC-RELATION entries.
                    * Optionally archives the generated .reqif output as a .reqifz ZIP archive.
                    * Optionally persists the identifiers of ReqIF Identifiable elements in a JSON store so that they stay immutable across consecutive exports.
                    """
                verification_criteria = "Call the tool using the `pyTRLCConverter` frontend with reqif output format."
                satisfies = [
                    SwRequirements.sw_req_reqif,
                    SwRequirements.sw_req_reqif_section,
                    SwRequirements.sw_req_reqif_record,
                    SwRequirements.sw_req_reqif_multiple_doc_mode,
                    SwRequirements.sw_req_reqif_single_doc_mode,
                    SwRequirements.sw_req_reqif_out_file_name_default,
                    SwRequirements.sw_req_reqif_out_file_name_custom,
                    SwRequirements.sw_req_reqif_top_level_default,
                    SwRequirements.sw_req_reqif_top_level_custom,
                    SwRequirements.sw_req_reqif_render_md,
                    SwRequirements.sw_req_reqif_render_gfm,
                    SwRequirements.sw_req_reqif_render_xhtml,
                    SwRequirements.sw_req_reqif_render_path,
                    SwRequirements.sw_req_reqif_render_table_options,
                    SwRequirements.sw_req_reqif_render_plantuml,
                    SwRequirements.sw_req_reqif_enum,
                    SwRequirements.sw_req_reqif_enum_key_order,
                    SwRequirements.sw_req_reqif_enum_null,
                    SwRequirements.sw_req_reqif_relation,
                    SwRequirements.sw_req_reqif_reqifz,
                    SwRequirements.sw_req_reqif_identifier_immutable,
                    SwRequirements.sw_req_reqif_identifier_store_init,
                    SwRequirements.sw_req_reqif_identifier_store_reuse,
                    SwRequirements.sw_req_destination_format
                ]
            }
        }
        section "DocX Converter" {
            Generic.PlantUML sw_arch_comp_docx_converter_diagram {
                    caption = "Class Diagram for DocX-Converter"
                    file_path ="../../doc/architecture/components/comp_docx_converter.puml"
            }
            SwArchSpec sw_arch_component_docx_converter {
                description =
                    """
                    The DocX Converter implements the DocX format output conversion.

                    * Registers the `docx` output format and options.
                    * Creates sections and records in docx format.
                    * Renders inline PlantUML fenced code blocks as embedded PNG images.
                    """
                verification_criteria = "Call the tool using the `pyTRLCConverter` frontend with docx output format."
                satisfies = [
                    SwRequirements.sw_req_docx,
                    SwRequirements.sw_req_docx_template,
                    SwRequirements.sw_req_docx_file,
                    SwRequirements.sw_req_docx_section,
                    SwRequirements.sw_req_docx_record,
                    SwRequirements.sw_req_docx_reference,
                    SwRequirements.sw_req_docx_render_md,
                    SwRequirements.sw_req_docx_render_gfm,
                    SwRequirements.sw_req_docx_render_plantuml,
                    SwRequirements.sw_req_destination_format
                ]
            }
        }

        section "Version Information" {
            Generic.PlantUML sw_arch_comp_version_diagram {
                    caption = "Class Diagram for Version"
                    file_path ="../../doc/architecture/components/comp_version.puml"
            }
            SwArchSpec sw_arch_component_version {
                description =
                    """
                    The version component handles version and other program attributes.
                    """
                verification_criteria = "Call the tool using the `pyTRLCConverter` frontend with --version to see version information."
                satisfies = [
                    SwRequirements.sw_req_version,
                    SwRequirements.sw_req_cli_version
                ]
            }
        }

        section "Logger" {
            Generic.PlantUML sw_arch_comp_logging_diagram {
                    caption = "Class Diagram for Logging"
                    file_path ="../../doc/architecture/components/comp_logger.puml"
            }
            SwArchSpec sw_arch_component_logging {
                description =
                    """
                    The Logger component provides a wrapper for Python logging to handle verbose and normal logging.
                    """
                verification_criteria = "Call the tool using the `pyTRLCConverter` frontend with and without --verbose."
                satisfies = [
                    SwRequirements.sw_req_verbose_mode
                ]
            }
        }

        section "PlantUML" {
            Generic.PlantUML sw_arch_comp_plantuml_diagram {
                    caption = "Class Diagram for PlantUML"
                    file_path ="../../doc/architecture/components/comp_plantuml.puml"
            }
            SwArchSpec sw_arch_component_plantuml {
                description =
                    """
                    The PlantIML component provides diagram image generation based on PlantUML files.
                    """
                verification_criteria = "Convert TRLC files with PlantUML items to markdown, rst and docx."
                satisfies = [
                    SwRequirements.sw_req_plantuml
                ]
            }
        }
    }
}
