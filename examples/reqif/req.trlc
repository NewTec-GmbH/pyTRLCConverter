package Requirements

// The first section name is used to specify the ReqIF top level specification.
section "ReqIF TRLC Example" {

    Information inf_intro {
        description = "This document contains the ReqIF TRLC example."
        status = Status.Draft
    }

    Image img_test {
        file_path = "../../doc/images/NewTec_Logo.png"
        caption = "The caption of the image."
        status = Status.Draft
    }

    Requirement req_plain_text {
        name = "plain text"
        description = "This requirements is written with plain text."
        status = Status.Draft
    }

    Requirement req_table {
        name = "table"
        description =
        '''
        | Column 1 | Column 2 |
        | -------- | -------- |
        | A        | B        |
        '''
        status = Status.Draft
    }

    Heading hdr_my_childs {
        description = "Heading for my children"
    }

    section "Children" {

        Requirement req_child_1 {
            name = "child 1"
            description = "This requirements is child 1."
            status = Status.Draft
        }

        Requirement req_child_2 {
            name = "child 2"
            description = "This requirements is child 2."
            derived = [Requirements.req_child_1]
            status = Status.Draft
        }
    }
}
