# Specification: req

## spec-object-1: plain text (Requirement)
This requirements is written with plain text.
- External ID: req_plain_text
- derived: N/A
- Status: Status.Draft

## spec-object-3: table (Requirement)
| Column 1 | Column 2 |
| --- | --- |
| A | B |
- External ID: req_table
- derived: N/A
- Status: Status.Draft

## spec-object-5: Children (Section)

### spec-object-7: child 1 (Requirement)
This requirements is child 1.
- External ID: req_child_1
- derived: N/A
- Status: Status.Draft

### spec-object-9: child 2 (Requirement)
This requirements is child 2.
- External ID: req_child_2
- Status: Status.Draft
- derived -> spec-object-7
